FME workspace inReachOnly.fmw

Parameters:
- SourceDataset_OGCKML_8 = http://bit.ly/2z75naZ" "http://bit.ly/2juRkVY" "http://bit.ly/2huJ3Nf" "http://bit.ly/2AOpbgJ   # Source Google KML File or URL

Readers:
- OGCKML_1: OGCKML from $(SourceDataset_OGCKML_8)
- ARCGISONLINEFEATURES_1: ARCGISONLINEFEATURES

Writers:
- ARCGISONLINEFEATURES_3: ARCGISONLINEFEATURES
- ARCGISONLINEFEATURES_4: ARCGISONLINEFEATURES

CoordinateSystemSetter
    COORDSYS = LL84
    -> AttributeRenamer_2
AttributeRenamer_2
    ATTR_TABLE = RENAME_SET_DEFAULT time > timeRecord
    -> StatisticsCalculator
    -> FeatureMerger [SUPPLIER]
    -> FeatureMerger_2 [SUPPLIER]
StatisticsCalculator
    MEAN_ATTR = _mean
    RANGE_ATTR = _range
    MODE_ATTR = _mode
    MAX_ATTR = _max
    GROUP_BY = name
    SUM_ATTR = _sum
    NUMERIC_ATTR = _numeric_count
    STDEVP_ATTR = _stdevp
    STATS_ATTRS = timeRecord
    COUNT_ATTR = _count
    STDEV_ATTR = _stdev
    MIN_ATTR = _min
    COMPUTE_HISTOGRAM = NO
    MEDIAN_ATTR = _median
    PREPEND_ATTR_NAME_CHOICE = For multiple results only
    SUMMARY -> FeatureMerger [REQUESTOR]
FeatureMerger
    ATTR_ACCUM_MODE = Only Use Supplier
    SUPPLIERS_FIRST = No
    PROCESS_DUPS = No
    REJECT_NULL_MISSING_KEYS = No
    JOIN_KEYS = @Value(name) @Value(name) AUTO @Value(_max) @Value(timeRecord) AUTO
    MERGE_TYPE = Attributes and Geometry
    MERGED -> StringReplacer_3

Bookmark: inReach Reader
Placemark (reader OGCKML_1)
    attributes: kml_data{0}.value kml_buffer, kml_data{1}.value kml_buffer, kml_data{2}.value kml_buffer, kml_data{3}.value kml_buffer, kml_data{4}.value kml_buffer, kml_data{5}.value kml_buffer, kml_data{6}.value kml_buffer, kml_data{7}.value kml_buffer, kml_data{8}.value kml_buffer, kml_data{9}.value kml_buffer, kml_data{10}.value kml_buffer, kml_data{11}.value kml_buffer, kml_data{12}.value kml_buffer, kml_data{13}.value kml_buffer, kml_data{14}.value kml_buffer, kml_data{15}.value kml_buffer, kml_data{16}.value kml_buffer
    -> VertexCreator_3
VertexCreator_3
    MODE_NAME = Add Point
    YVAL = @Value(kml_data{8}.value)
    XVAL = @Value(kml_data{9}.value)
    -> AttributeRenamer
AttributeRenamer
    ATTR_TABLE:
      RENAME_SET_DEFAULT kml_data{4}.value > name
      RENAME_SET_DEFAULT kml_data{0}.value > foreign_pk
      RENAME_SET_DEFAULT kml_data{12}.value > course
      RENAME_SET_DEFAULT kml_data{1}.value > time
    -> DateTimeConverter_2
DateTimeConverter_2
    IN_FORMAT = %N/%e/%Y %l:%M:%S %p
    DATETIME_ATTR = time
    OUT_FORMAT = ISO
    REPAIR_INPUT = NO
    -> AttributeCreator_2
AttributeCreator_2
    ATTR_TABLE = SET_TO device = inReach
    -> StringReplacer_2
StringReplacer_2
    REGEXP = YES
    CASE = NO
    FIND_TEXT = [A-z °/]
    SRC_ATTRS = course
    NO_MATCH = _FME_NO_OP_
    -> CoordinateSystemSetter

Bookmark: Calculates time since present
StringReplacer_3
    REGEXP = NO
    CASE = NO
    FIND_TEXT = Z
    SRC_ATTRS = timeRecord
    NO_MATCH = _FME_NO_OP_
    -> DateTimeConverter_3
DateTimeConverter_3
    IN_FORMAT = ISO
    DATETIME_ATTR = timeRecord
    OUT_FORMAT = FME
    REPAIR_INPUT = NO
    -> DateTimeCalculator_2
DateTimeCalculator
    OPERATION_PARAMETERS = DATETIME_GROUP]]START_DATETIME]@Value(hackTime)]END_DATETIME]@DateTimeNow()]RESULT_GROUP]]RESULT_TYPE]MINUTES]RESULT_INTERVAL]timeSincePresent]FME_CONTROLLER_QUERY_FILE]transformers/dependencies/datetimecalculator/DATETIMECALC_3_CALCULATE_INTERVAL.fme
    MODE = DATETIMECALC_3_CALCULATE_INTERVAL
    -> DateTimeConverter_4
DateTimeConverter_4
    IN_FORMAT = FME
    DATETIME_ATTR = timeRecord
    OUT_FORMAT = ISO
    REPAIR_INPUT = NO
    -> Latest_Location (writer ARCGISONLINEFEATURES_4)

Bookmark: Horrible Hack
  I had trouble with the time zones, so I just added 420 minutes to correct the MST vs UTC issue. Will probably break around a change in daylight time savings switch.
DateTimeCalculator_2
    OPERATION_PARAMETERS = DATETIME_GROUP]]START_DATETIME]@Value(timeRecord)]OPERATOR]SUBTRACT]YEARS]0]MONTHS]0]DAYS]0]HOURS]0]MINUTES]420]SECONDS]0]RESULT_GROUP]]RESULT_DATETIME]hackTime]FME_CONTROLLER_QUERY_FILE]transformers/dependencies/datetimecalculator/DATETIMECALC_1_ADD_INTERVAL.fme
    MODE = DATETIMECALC_1_ADD_INTERVAL
    -> DateTimeCalculator

Bookmark: Write to ArcGIS
Latest_Location (writer ARCGISONLINEFEATURES_4)
    attributes: name esriFieldTypeString(256), timeRecord esriFieldTypeDate, course esriFieldTypeDouble, device esriFieldTypeString(256), foreign_pk esriFieldTypeString(256), timeSincePresent esriFieldTypeInteger
Location Tracking (writer ARCGISONLINEFEATURES_3)
    attributes: device esriFieldTypeString(200), name esriFieldTypeString(254), foreign_pk esriFieldTypeString(200), course esriFieldTypeDouble, timeRecord esriFieldTypeDate

Bookmark: Read from ArcGIS
Location Tracking (reader ARCGISONLINEFEATURES_1)
    attributes: OBJECTID esriFieldTypeOID, GlobalID esriFieldTypeGlobalID(38), CreationDate esriFieldTypeDate, Creator esriFieldTypeString(50), EditDate esriFieldTypeDate, Editor esriFieldTypeString(50), name esriFieldTypeString(256), timeRecord esriFieldTypeDate, course esriFieldTypeDouble, device esriFieldTypeString(256), foreign_pk esriFieldTypeString(256)
    -> FeatureMerger_2 [REQUESTOR]

Bookmark: Check for Updates
Note: Bread crumb table
FeatureMerger_2
    ATTR_ACCUM_MODE = Merge Supplier
    SUPPLIERS_FIRST = No
    ATTR_CONFLICT_RES = Use Requestor
    IGNORE_NULLS = No
    PROCESS_DUPS = No
    REJECT_NULL_MISSING_KEYS = No
    JOIN_KEYS = @Value(foreign_pk) @Value(foreign_pk) AUTO
    MERGE_TYPE = Attributes Only
    UNUSED_SUPPLIER -> Location Tracking (writer ARCGISONLINEFEATURES_3)
